(princ "Test #1\n")
(princ (strcat "<|" (read-line) "|>\n"))
(princ (strcat "<|" (read-line) "|>\n"))
(princ (strcat "<|" (read-line) "|>\n"))

(princ "Test #2\n")
(princ (strcat "<|" (read-line) "|>\n"))
(princ (strcat "<|" (read-line) "|>\n"))

(princ "Test #3\n")
(princ (strcat "<|" (read-line) "|>\n"))

(princ "Test #4\n")
(princ (strcat "<|" (read-line) "|>\n"))
(princ (strcat "<|" (read-line) "|>\n"))
